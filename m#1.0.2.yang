module m {
    yang-version 1.1;
    namespace "urn:m";
    prefix m;
    rev:revision-label-scheme "ysver:yang-semver";

    import ietf-yang-revisions {
        rev:recommended-min "3.3.3";
        prefix rev;
    }
    import ietf-yang-semver {
        rev:recommended-min "2.2.2";
        prefix ysver;
    }

    revision 2023-11-05 {
        rev:label "1.0.1";
    }
    revision 2023-11-04 {
        rev:label "1.0.2";
    }
    revision 2023-11-03 {
        rev:label "1.0.0";
    }
}
