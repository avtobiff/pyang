module m {
    yang-version 1.1;
    namespace "urn:m";
    prefix m;
    rev:revision-label-scheme "ysver:yang-semver";

    import ietf-yang-revisions {
        prefix rev;
    }
    /* import ietf-yang-semver {
        rev:recommended-min "1.0.0";
        prefix ysver;
    } */

    revision 2023-11-04 {
        rev:label "1.0.0";
    }
}
